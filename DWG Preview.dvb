Attribute VB_Name = "frmpreview"
Attribute VB_Base = "0{848E0698-8964-429E-9976-04E4FA8BA8EF}{720D6589-1C83-4D76-B643-C8E9666D85B9}"
Attribute VB_GlobalNameSpace = False
Attribute VB_Creatable = False
Attribute VB_PredeclaredId = True
Attribute VB_Exposed = False
Attribute VB_TemplateDerived = False
Attribute VB_Customizable = False

Option Explicit

'///API FOR RETURN FOLDER DIALOG///
Private Declare Function SHBrowseForFolder _
Lib "shell32.dll" Alias "SHBrowseForFolderA" _
(lpBrowseInfo As BROWSEINFO) As Long

Private Declare Function SHGetPathFromIDList _
Lib "shell32.dll" Alias "SHGetPathFromIDListA" _
(ByVal pidl As Long, ByVal pszPath As String) _
As Long

Private Type BROWSEINFO
  hOwner As Long
  pidlRoot As Long
  pszDisplayName As String
  lpszTitle As String
  ulFlags As Long
  lpfn As Long
  lParam As Long
  iImage As Long
End Type

Private Const MAX_PATH = 2600

'///END API FOR THE RETURN FOLDER DIALOG///

'/// BEGIN API FOR THE BITMAP & PAINT////

Private Type BITMAPINFOHEADER
  biSize As Long
  biWidth As Long
  biHeight As Long
  biPlanes As Integer
  biBitCount As Integer
  biCompression As Long
  biSizeImage As Long
  biXPelsPerMeter As Long
  biYPelsPerMeter As Long
  biClrUsed As Long
  biClrImportant As Long
End Type


Private Type RGBQUAD
  rgbBlue As Byte
  rgbGreen As Byte
  rgbRed As Byte
  rgbReserved As Byte
End Type

Private Type IMGREC
  bytType As Byte
  lngStart As Long
  lngLen As Long
End Type

Private Type RECT
    Left As Long
    Top As Long
    Right As Long
    Bottom As Long
End Type
'The all important Type - RECT
'Contains the coordinates (relative to the Window's DC that we are
'Using)

Private Const WM_PAINT = &HF
Private Const BDR_SUNKENOUTER = &H2
Private Const BDR_RAISEDINNER = &H4
Private Const EDGE_ETCHED = (BDR_SUNKENOUTER Or BDR_RAISEDINNER)
'These are all of the different styles that can be used as an edge
Private Const BF_BOTTOM = &H8
Private Const BF_LEFT = &H1
Private Const BF_RIGHT = &H4
Private Const BF_TOP = &H2
Private Const BF_RECT = (BF_LEFT Or BF_TOP Or BF_RIGHT Or BF_BOTTOM)
'And the constants that define which side of the rectangle to draw
'On, with BF_RECT being all four sides


Private Declare Function ReleaseDC Lib "user32" _
(ByVal hwnd As Long, ByVal hdc As Long) As Long
'This releases the Device Context for the window that we
'Are going to draw on.

Private Declare Function SetRect Lib "user32" _
(lpRect As RECT, ByVal X1 As Long, ByVal Y1 As Long, _
ByVal X2 As Long, ByVal Y2 As Long) As Long
'Uses the values passed to it to define a rectangular
'Area on the screen.

Private Declare Function DrawEdge Lib "user32" _
(ByVal hdc As Long, qrc As RECT, ByVal edge As Long, _
ByVal grfFlags As Long) As Long


Private Declare Function GetDC Lib "user32" _
(ByVal hwnd As Long) As Long

Private Declare Function FindWindow Lib _
"user32" Alias "FindWindowA" (ByVal lpClassName _
As String, ByVal lpWindowName As String) As Long

Private Declare Function SetPixel Lib _
"gdi32" (ByVal hdc As Long, ByVal X As _
Long, ByVal Y As Long, ByVal crColor _
As Long) As Long

'///END API FOR BITMAP & PAINT///

'A variable to hold found files from the
'FindFile method
Private cFiles As Collection
Dim RC As RECT



Private Sub UserForm_Activate()
  Dim strBlank As String
  '/Initialize Begins
  Me.Caption = "Drawing Explorer"
  '/Frame 1 Controls
  Frame1.Caption = " File Info "
  ComboBox1.AddItem Application.Path
  ComboBox1.AddItem "Browse"
  Set cFiles = New Collection
End Sub

Private Sub ComboBox1_Click()
  Dim strPath As String
  Dim lngCnt As Long
  Static blnCode As Boolean
  'This keeps the code from
  'Becoming recursive when it
  'Set the Index to a new item
  '(This will fir the click event
  'Again)
  If Not blnCode Then
  If ComboBox1.Text = "Browse" Then
    strPath = ReturnFolder
    If Len(strPath) > 0 Then
      ComboBox1.AddItem strPath, _
      ComboBox1.ListCount - 1
      blnCode = True
      ComboBox1.ListIndex = _
      ComboBox1.ListCount - 2
    Else
      ComboBox1.Text = vbNullString
    End If
  Else
    strPath = ComboBox1.Text
  End If
  'Remove all of the old file names
  ResetFiles
  'Change False to true and you can
  'Get files from the sub folders..
  FindFile strPath, "dwg", False
  ListBox1.Clear
  For lngCnt = 1 To FileCount
    ListBox1.AddItem GetFile(lngCnt)
  Next lngCnt
  Else
    blnCode = Not blnCode
  End If
End Sub

Private Sub ListBox1_Click()
    Call PaintPreview(ListBox1.Text)
End Sub

'//Display the Browse For Folder Dialog ///

Private Function ReturnFolder() As String
  Dim Browser As BROWSEINFO
  Dim lngFolder As Long
  Dim strPath As String
  On Error GoTo Err_Control
  With Browser
    .hOwner = 0&
    .lpszTitle = "Select Directory to work in"
    .pszDisplayName = String(MAX_PATH, 0)
  End With
  strPath = String(MAX_PATH, 0)
  lngFolder = SHBrowseForFolder(Browser)
  If lngFolder Then
    SHGetPathFromIDList lngFolder, strPath
    ReturnFolder = Left(strPath, InStr(strPath, _
    vbNullChar) - 1)
  End If
Exit_Here:
  Exit Function
Err_Control:
  Select Case Err.Number
  'Add your Case selections here
    Case Else
    MsgBox Err.Description
    Resume Exit_Here
  End Select
End Function

'//Search for files

Public Sub FindFile(StartPath As String, _
Extension As String, GetSubs As Boolean)
  Dim strFileName As String
  Dim cDir As New Collection
  Dim intCnt As Integer
  On Error GoTo Err_Control
  If Len(StartPath) > 0 Then
  If Right(StartPath, 1) <> "\" Then
    StartPath = StartPath & "\"
  End If
  strFileName = Dir(StartPath & "*.*", _
  vbDirectory)
  Do While (strFileName <> "")
  'Don't want the DOS Dots
    If Not strFileName = "." And Not _
    strFileName = ".." Then
      If StrComp(Right(strFileName, 3), _
      Extension, vbTextCompare) = 0 Then
        cFiles.Add StartPath & strFileName
      ElseIf GetAttr(StartPath & strFileName) = _
      vbDirectory Then
        cDir.Add StartPath & strFileName
      End If
    End If
    strFileName = Dir
    'Just in case someone does a search
    'From the root of a BIG drive
    DoEvents
  Loop
  If GetSubs Then
    If (cDir.Count > 0) Then
      For intCnt = 1 To cDir.Count
        FindFile cDir(intCnt), Extension, True
      Next intCnt
    End If
  End If
  Set cDir = Nothing
  End If
Exit_Here:
  Exit Sub
Err_Control:
  Select Case Err.Number
  'Add your Case selections here
    Case Else
    MsgBox Err.Description
    Resume Exit_Here
  End Select
End Sub

'After FindFile is run, this will return
'The count of files found!
Private Property Get FileCount() As Long
  FileCount = cFiles.Count
End Property

'Get the path of a file in the cFiles collection
Private Function GetFile(lngID As Long) As String
  On Error GoTo Err_Control
  GetFile = cFiles(lngID)
Exit_Here:
  Exit Function
Err_Control:
  Select Case Err.Number
  'Add your Case selections here
    Case Else
    MsgBox Err.Description
    Resume Exit_Here
  End Select
End Function

'Fast way to clear the collection
Private Sub ResetFiles()
  Set cFiles = New Collection
End Sub

Public Function PaintPreview(strFile As String) As Integer
  Dim lngSeeker As Long
  Dim lngImgLoc As Long
  Dim bytCnt As Byte
  Dim lngFile As Long
  Dim lngCurLoc As Long
  Dim intCnt As Integer
  Dim udtRec As IMGREC
  Dim bytBMPBuff() As Byte
  Dim udtColors() As RGBQUAD
  Dim udtColor As RGBQUAD
  Dim lngHwnd As Long
  Dim lngDc As Long
  Dim lngY As Long
  Dim lngX As Long
  Dim intRed As Integer
  Dim intGreen As Integer
  Dim intBlue As Integer
  Dim lngColor As Long
  Dim lngCnt As Long
  Dim udtHeader As BITMAPINFOHEADER
  On Error GoTo Err_Control
  If Len(Dir(strFile)) > 0 Then
    lngFile = FreeFile
    Open strFile For Binary As lngFile
    Seek lngFile, 14
    Get lngFile, , lngImgLoc
    Seek lngFile, lngImgLoc + 17
    lngCurLoc = Seek(lngFile)
    Seek lngFile, lngCurLoc + 4
    Get lngFile, , bytCnt
    If bytCnt > 1 Then
      For intCnt = 1 To bytCnt
        Get lngFile, , udtRec
        If udtRec.bytType = 2 Then
        'All of the code preceding this Line
        'Is identical to the code in Part
        'Two of Byte By Byte.
        'Now we begin the color extraction
        'The start value is the BYTE BEFORE
        'The BMP Header data (The RGBQUAD
        'And BMP Header are contained within
        'Another structure), so move the read/
        'Write marker to the next byte...
          Seek lngFile, udtRec.lngStart + 1
          'Pull out the BMP header data...
          Get lngFile, , udtHeader
          'Resize the Byte buffer to the full
          'Length of the data...
          ReDim bytBMPBuff(udtRec.lngLen)
          'Did you read Randall's article?
          If udtHeader.biBitCount = 8 Then
            'Resize the array of RGBQuads, I
            'Could also have used the biClrUsed
            'Value of the udtHeader...
            ReDim udtColors(256)
            'Grab all of the color values
            Get lngFile, , udtColors
            'Now we grab the full record by
            'Moving the Read/Write marker
            'Back to the start of the data.
            'Don't worry about all of the data
            'We allready grabbed...
            '(If you read Randall's article,
            'Remember that the data is reverse
            'Scan...
            Seek lngFile, udtRec.lngStart
            'Fill the buffer...
            Get lngFile, , bytBMPBuff
            'Now grab the Forms Handle
            lngHwnd = FindWindow(vbNullString, Me.Caption)
            'So we can get its Device Context..
            lngDc = GetDC(lngHwnd)
            'I thought this was a nice touch..
            Me.Caption = strFile
            'Clean any old paint off..
            Me.Repaint
            'Begin Painting
            
            For lngY = 1 To udtHeader.biHeight
              For lngX = udtHeader.biWidth To _
              1 Step -1
                'See, we are reading the data
                'From THE END of the buffer...
                lngColor = _
                bytBMPBuff((UBound(bytBMPBuff) - lngCnt))
                'Get the mapped value
                udtColor = udtColors(lngColor)
                'Break it into Red
                intRed = CInt(udtColor.rgbRed)
                'Green
                intGreen = CInt(udtColor.rgbGreen)
                'And Blue
                intBlue = CInt(udtColor.rgbBlue)
                'Get a color the API will accept
                lngColor = RGB(intRed, intGreen, intBlue)
                'Paint this Pixel. The + 5 is to
                'Give a little offset from the edge
                'Of the form.
                'But before we do, would you like
                'To have Black backgrounds? Easy,
                'Swap the map:
                '///BLACK BACKGROUND///
                If lngColor = vbBlack Then
                  lngColor = vbWhite
                ElseIf lngColor = vbWhite Then
                  lngColor = vbBlack
                End If
                '//////////////////////
                'If your prefere White (the true Value) Then just remove that..
                SetPixel lngDc, lngX + 20, lngY + 25, lngColor
                'Increment the counter...
                lngCnt = lngCnt + 1
              Next lngX
            Next lngY
            'NEW//FRAME
            SetRect RC, 20, 25, udtHeader.biWidth + 20, udtHeader.biHeight + 25
            DrawEdge lngDc, RC, BDR_SUNKENOUTER, BF_RECT
          End If
          Exit For
        ElseIf udtRec.bytType = 3 Then
          'Its a Meta File!
          Exit For
        End If
      Next intCnt
    Else
      'Print Message - No Preview
    End If
    'Close the file
    Close lngFile
    'Return the value
  End If
  ReleaseDC lngHwnd, lngDc
  'General Error control
Exit_Here:
  Exit Function
Err_Control:
  Select Case Err.Number
  'Add your Case selections here
    Case Else
    MsgBox Err.Description
    Resume Exit_Here
  End Select
End Function

Private Sub UserForm_QueryClose(Cancel As _
Integer, CloseMode As Integer)
  On Error GoTo Err_Control
  Set cFiles = Nothing
Exit_Here:
  Exit Sub
Err_Control:
  Select Case Err.Number
  'Add your Case selections here
    Case Else
    MsgBox Err.Description
    Resume Exit_Here
  End Select
End Sub
